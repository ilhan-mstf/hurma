OPENSTAGEPHONE-MIB DEFINITIONS ::= BEGIN

   IMPORTS
       MODULE-IDENTITY,
       OBJECT-TYPE,
       NOTIFICATION-TYPE,
       IpAddress,
       enterprises
           FROM SNMPv2-SMI
       TEXTUAL-CONVENTION
           FROM SNMPv2-TC;

-- Some MIB compilers require that the following 2 lines
-- which define the path to this MIB are added.

--  mgmt              OBJECT IDENTIFIER ::= { iso org(3) dod(6) internet(1) mgmt(2) }
--  mib               OBJECT IDENTIFIER ::= { mgmt 1 }
  siemens	          OBJECT IDENTIFIER ::= { enterprises 4329 }
  iandcAdmin	    OBJECT IDENTIFIER ::= { siemens 2 }
  ipPhones		    OBJECT IDENTIFIER ::= { iandcAdmin 38 }


--  Siemens OpenStage Phone MIB

openStagePhones MODULE-IDENTITY
    LAST-UPDATED "200802210000Z"
    ORGANIZATION "Siemens Enterprise Communications"
    CONTACT-INFO
        "Eda Kilic
         Postal: Siemens Enterprise Communications
         ODTU Teknokent,
         Galyum Bina , 2. Kat
         06531 Ankara
         Turkey
         Phone:  +90 312 292 6033
         Email:  eda.kilic@siemens.com"
    DESCRIPTION
        "The MIB module for interpreting SIP and CorNet related traps from Siemens OpenStage phones"
    ::= { ipPhones 3 }

--  Textual Conventions
BooleanValue ::= TEXTUAL-CONVENTION
      STATUS current
      DESCRIPTION
      "A value that can be true(1) or false(0)."
      SYNTAX    INTEGER { false(0), true(1) }

-- ++++++++++++++++++++++++++++++++++++++++++++++++++++++++++++++++++++++++
--                                                                        |
--        Phone types in the OpenStage family                             |
--                                                                        |
-- ++++++++++++++++++++++++++++++++++++++++++++++++++++++++++++++++++++++++

phoneDeviceTypes      OBJECT IDENTIFIER ::= { openStagePhones 1 }

openStage20 OBJECT-TYPE
	SYNTAX  DisplayString (SIZE (0..255))
	MAX-ACCESS  read-only
	STATUS      current
	DESCRIPTION
	   "To allow sysObjectId in MIB2 to be assigned an object id for OpenStage 20
          phone type."
	::= { phoneDeviceTypes 1 }

openStage40 OBJECT-TYPE
	SYNTAX  DisplayString (SIZE (0..255))
	MAX-ACCESS  read-only
	STATUS      current
	DESCRIPTION
	   "To allow sysObjectId in MIB2 to be assigned an object id for OpenStage 40
          phone type."
	::= { phoneDeviceTypes 2 }

openStage60 OBJECT-TYPE
	SYNTAX  DisplayString (SIZE (0..255))
	MAX-ACCESS  read-only
	STATUS      current
	DESCRIPTION
	   "To allow sysObjectId in MIB2 to be assigned an object id for OpenStage 60
          phone type."
	::= { phoneDeviceTypes 3 }

openStage80 OBJECT-TYPE
	SYNTAX  DisplayString (SIZE (0..255))
	MAX-ACCESS  read-only
	STATUS      current
	DESCRIPTION
	   "To allow sysObjectId in MIB2 to be assigned an object id for OpenStage 80
          phone type."
	::= { phoneDeviceTypes 4 }

openStage20E OBJECT-TYPE
	SYNTAX  DisplayString (SIZE (0..255))
	MAX-ACCESS  read-only
	STATUS      current
	DESCRIPTION
	   "To allow sysObjectId in MIB2 to be assigned an object id for OpenStage 20E
          phone type."
	::= { phoneDeviceTypes 5 }

openStage15 OBJECT-TYPE
	SYNTAX  DisplayString (SIZE (0..255))
	MAX-ACCESS  read-only
	STATUS      current
	DESCRIPTION
	   "To allow sysObjectId in MIB2 to be assigned an object id for OpenStage 15
          phone type."
	::= { phoneDeviceTypes 6 }



-- ++++++++++++++++++++++++++++++++++++++++++++++++++++++++++++++++++++++++
--                                                                        |
--        The Traps generated by the phone                                |
--                                                                        |
-- ++++++++++++++++++++++++++++++++++++++++++++++++++++++++++++++++++++++++

phoneAlarms         OBJECT IDENTIFIER ::= { openStagePhones 2 }

-- ++++++++++++++++++++++++++++++++++++++++++++++++++++++++++++++++++++++++
--        The variable binding list items in the traps                    |
-- ++++++++++++++++++++++++++++++++++++++++++++++++++++++++++++++++++++++++

phoneAlarmDetail    OBJECT IDENTIFIER ::= { phoneAlarms 1 }

-- ++++++++++++++++++++++++++++++++++++++++++++++++++++++++++++++++++++++++
--        Phone identity                                                  |
-- ++++++++++++++++++++++++++++++++++++++++++++++++++++++++++++++++++++++++

phoneIdentity       OBJECT IDENTIFIER ::= { phoneAlarmDetail 1 }

phoneMacAddress OBJECT-TYPE
	SYNTAX  OCTET STRING (SIZE (0..6))
	MAX-ACCESS  read-only
	STATUS      current
	DESCRIPTION
	   "MAC Address of the OpenStage phone"
	::= { phoneIdentity 1 }

phoneIpAddress OBJECT-TYPE
	SYNTAX  IpAddress
	MAX-ACCESS  read-only
	STATUS      current
	DESCRIPTION
	   "IP Address of the OpenStage phone"
	::= { phoneIdentity 2 }

phoneNumber OBJECT-TYPE
	SYNTAX  DisplayString (SIZE (0..255))
	MAX-ACCESS  read-only
	STATUS      current
	DESCRIPTION
	   "SIP: URI assigned to the primary line on the SIP phone
          (e.g. mike@siemens.com or 1234@siemens.com),
          or NONE if no URI has been assigned.
          CorNet: Fully qualified subscriber number."
	::= { phoneIdentity 3 }

phoneType OBJECT-TYPE
	SYNTAX  INTEGER {
                 CorNet(1),
                 SIP(2)
              }
	MAX-ACCESS  read-only
	STATUS      current
	DESCRIPTION
	   "Type of software, CorNet or SIP, installed on the phone."
	::= { phoneIdentity 4 }

-- ++++++++++++++++++++++++++++++++++++++++++++++++++++++++++++++++++++++++
--        Diagnostic Trace Events                                         |
-- ++++++++++++++++++++++++++++++++++++++++++++++++++++++++++++++++++++++++

diagnosticTraceEvent      OBJECT IDENTIFIER ::= { phoneAlarmDetail 2 }

phoneComponent OBJECT-TYPE
	SYNTAX  INTEGER {
                 AdminPhonelet(0),
                 CallLogPhonelet(1),
                 CallViewPhonelet(2),
                 PhonebookPhonelet(3),
                 HelpPhonelet(4),
                 ApplicationMenuPhonelet(5),
                 CertificateManagementService(6),
                 CommunicationsService(7),
                 ComponentRegistrarService(8),
                 CstaService(9),
                 DataAccessService(10),
                 DigitAnalysisService(11),
                 DigitalDataService(12),
                 DirectoryService(13),
                 DlsClientManagementService(14),
                 HealthService(15),
                 InstrumentationService(16),
                 JournalService(17),
                 MediaControlService(18),
                 MediaProcessingService(19),
                 MobilityService(20),
                 ObexService(21),
                 ClientManagementService(22),
                 PotService(23),
                 PasswordManagementService(24),
                 PhysicalInterfaceService(25),
                 SidecarService(26),
                 TeamService(27),
                 ToneGenerationService(28),
                 TransportService(29),
                 VoiceEngineServic(30),
                 WebService(31),
                 SipSignalling(32),
                 SipCallControl(33),
                 SipMessages(34),
                 ApplicationFramework(35),
                 DesktopPhonelet(36),
                 JavaPhonelet(37),
                 ServiceFramework(38),
                 ServiceRegistry(39),
                 BluetoothService(40),
                 MessagingService(41),
                 VcardParserService(42),
                 VoiceMailPhonelet(43),
                 UsbBackupService(44),  
                 Dot1xService(45),  
                 VoiceRecognitionService(46),  
                 H323Messages(47),  
                 H235Security(48)  
              }
	MAX-ACCESS  read-only
	STATUS      current
	DESCRIPTION
	   "The phone software component being traced."
	::= { diagnosticTraceEvent 1 }

eventDateTime OBJECT-TYPE
	SYNTAX  DisplayString (SIZE (0..25))
	MAX-ACCESS  read-only
	STATUS      current
	DESCRIPTION
	   "UTC date and time when event occurred, in format YYYY-MM-DDThh:mm:ss±hh:mm"
	::= { diagnosticTraceEvent 2 }

eventDescription OBJECT-TYPE
	SYNTAX  DisplayString (SIZE (0..255))
	MAX-ACCESS  read-only
	STATUS      current
	DESCRIPTION
	   "Textual description of the event."
	::= { diagnosticTraceEvent 3 }

-- ++++++++++++++++++++++++++++++++++++++++++++++++++++++++++++++++++++++++
--        Certificate Events                                              |
-- ++++++++++++++++++++++++++++++++++++++++++++++++++++++++++++++++++++++++

certificateEvent      OBJECT IDENTIFIER ::= { phoneAlarmDetail 3 }

serialNumber OBJECT-TYPE
	SYNTAX  DisplayString (SIZE (0..255))
	MAX-ACCESS  read-only
	STATUS      current
	DESCRIPTION
	   "Serial number of the certificate."
	::= { certificateEvent 1 }

certificateUsage OBJECT-TYPE
	SYNTAX  INTEGER {
                 InbuiltDefault(1),
                 DlsManagement(2),
                 HttpsConfiguration(3),
                 WebBasedManagement(4),
                 Telephony(5),
                 Authentication(6),
                 LDAP(7),
                 WAP(8),
                 PCApplicationInterface(9),
                 SymphoniaServices(10)
              }
	MAX-ACCESS  read-only
	STATUS      current
	DESCRIPTION
	   "Phone interface secured by the certificate"
	::= { certificateEvent 2 }

clientCertificate OBJECT-TYPE
	SYNTAX  BooleanValue
	MAX-ACCESS  read-only
	STATUS      current
	DESCRIPTION
	   "If the certificate is a client certificate from the phone perspective."
	::= { certificateEvent 3 }

expiryDate OBJECT-TYPE
	SYNTAX  DisplayString (SIZE (0..25))
	MAX-ACCESS  read-only
	STATUS      current
	DESCRIPTION
	   "UTC date and time when the certificate will expire, in format YYYY-MM-DDThh:mm:ss±hh:mm"
	::= { certificateEvent 4 }


-- ++++++++++++++++++++++++++++++++++++++++++++++++++++++++++++++++++++++++
--        The major alarms reported                                       |
-- ++++++++++++++++++++++++++++++++++++++++++++++++++++++++++++++++++++++++

phoneMajorAlarm        OBJECT IDENTIFIER ::= { phoneAlarms 2 }


traceEventFatal NOTIFICATION-TYPE
	  OBJECTS  { phoneMacAddress, phoneIpAddress, phoneNumber, phoneType, 
                   phoneComponent, eventDateTime, eventDescription }
	  STATUS current
	  DESCRIPTION
	     "Tracing has detected a fatal error."
	  ::= { phoneMajorAlarm 1 }

traceEventError NOTIFICATION-TYPE
	  OBJECTS  { phoneMacAddress, phoneIpAddress, phoneNumber, phoneType, 
                   phoneComponent, eventDateTime, eventDescription }
	  STATUS current
	  DESCRIPTION
	     "Tracing has detected a non-fatal error."
	  ::= { phoneMajorAlarm 2 }

certificateExpiryWarning NOTIFICATION-TYPE
	  OBJECTS  { phoneMacAddress, phoneIpAddress, phoneNumber, phoneType, 
                   serialNumber, certificateUsage, clientCertificate, expiryDate }
	  STATUS current
	  DESCRIPTION
	     "A certificate will expire soon."
	  ::= { phoneMajorAlarm 3 }

certificateExpired NOTIFICATION-TYPE
	  OBJECTS  { phoneMacAddress, phoneIpAddress, phoneNumber, phoneType, 
                   serialNumber, certificateUsage, clientCertificate, expiryDate }
	  STATUS current
	  DESCRIPTION
	     "A certificate has expired."
	  ::= { phoneMajorAlarm 4 }

END
